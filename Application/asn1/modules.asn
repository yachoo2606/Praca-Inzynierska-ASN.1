Requests DEFINITIONS ::= BEGIN

    Connected ::= SEQUENCE{
        name     UTF8String,
        number      INTEGER,
        connected   BOOLEAN
    }

    Request ::= SEQUENCE{
        name       UTF8String,
        column     INTEGER,
        row        INTEGER
    }

    Response ::= SEQUENCE{
        name       UTF8String,
        column     INTEGER,
        row        INTEGER,
        hit        BOOLEAN,
        sunk       BOOLEAN
    }

    Ready ::= SEQUENCE{
        name      UTF8String,
        ready      BOOLEAN
    }

END
